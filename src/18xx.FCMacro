import FreeCAD
import Part
from FreeCAD import Vector

import importlib

import constants
from Inserts.common.colours import Colour

importlib.reload(constants) # force FreeCAD to reload modules

from Inserts.common import geometry, cylinders, pencil, fuser, colours, smartbox, magnets, labels, smartsolid, primitives, hexes, hexagon

importlib.reload(geometry) # force FreeCAD to reload modules
importlib.reload(cylinders) # force FreeCAD to reload modules
importlib.reload(pencil) # force FreeCAD to reload modules
importlib.reload(fuser) # force FreeCAD to reload modules
importlib.reload(colours) # force FreeCAD to reload modules
importlib.reload(smartbox) # force FreeCAD to reload modules
importlib.reload(magnets) # force FreeCAD to reload modules
importlib.reload(labels) # force FreeCAD to reload modules
importlib.reload(smartsolid) # force FreeCAD to reload modules
importlib.reload(primitives) # force FreeCAD to reload modules
importlib.reload(hexes) # force FreeCAD to reload modules
importlib.reload(hexagon) # force FreeCAD to reload modules

from Inserts import company, lidbox, markerbox, cardbox, cubebox
importlib.reload(lidbox) # force FreeCAD to reload modules
importlib.reload(company) # force FreeCAD to reload modules
importlib.reload(markerbox) # force FreeCAD to reload modules
importlib.reload(cardbox) # force FreeCAD to reload modules
importlib.reload(cubebox) # force FreeCAD to reload modules

from Inserts.hex import configuration, images
importlib.reload(configuration) # force FreeCAD to reload modules
importlib.reload(images) # force FreeCAD to reload modules

from Inserts.hex import condensed
importlib.reload(condensed) # force FreeCAD to reload modules

from Inserts.games import insert1822PNW
importlib.reload(insert1822PNW) # force FreeCAD to reload modules


document = FreeCAD.newDocument('18xx-v6-rev')

# FreeCAD.Gui.activeDocument().activeView().viewIsometric()
# FreeCAD.Gui.activeDocument().activeView().viewLeft()
# FreeCAD.Gui.activeDocument().activeView().viewFront()
FreeCAD.Gui.activeDocument().activeView().viewTop()
# FreeCAD.Gui.activeDocument().activeView().viewBottom()
# FreeCAD.Gui.runCommand('Std_DrawStyle', 6)
#
# fuser = insert1822PNW.createMarkerBox(document)
# fuser.translate(Vector(0, 0, -0.2))
# fuser.show(50)


# fuser = insert1822PNW.createTileBoard(document, *[None]*2, "P1", "P2")
# fuser = insert1822PNW.createYellowTileBoard(document)
fuser = insert1822PNW.createGrayTileBoard(document)
# fuser = insert1822PNW.createGreenTileBoard(document)
# fuser = insert1822PNW.createBrownTileBoard(document)
# fuser = insert1822PNW.createMarkerBox(document)
# fuser = insert1822PNW.createMarkerBoxLid(document)
# fuser = insert1822PNW.createCardBox()
# fuser = insert1822PNW.createCubedBox()
# fuser = insert1822PNW.createCubedBoxLid()
# fuser = insert1822PNW.createCompanyBox()
# fuser = insert1822PNW.createTileBoardLid()

# fuser = insert1822PNW.createImage(document)

# a = fuser.translate(Vector(0, 0, 11.2)).getResult()
# b = a.copy()
# b.translate(Vector(54.84, 0, 0))

# f =Part.show(a)
# f.ViewObject.Transparency = 20
# f.ViewObject.ShapeColor = Colour.GREEN.decode()

# f =Part.show(b)
# f.ViewObject.Transparency = 20
# f.ViewObject.ShapeColor = Colour.BLUE.decode()
fuser.show(0)

# fuserBox.show(80)


# insert1822PNW.createBoard()

FreeCAD.Gui.SendMsgToActiveView('ViewFit')
